# SPDX-License-Identifier: LGPL-2.1-or-later
# SPDX-FileNotice: Part of the FreeCAD project.

# Classic theme must delete any set value for the editor text so that it is calculated dynamically when needed
import FreeCAD

editorPrefs = FreeCAD.ParamGet("User parameter:BaseApp/Preferences/Mod/Editor")
editorPrefs.RemInt("Text")

appPrefs = FreeCAD.ParamGet("User parameter:BaseApp/Preferences/MainWindow")
appPrefs.RemString("QtStyle")
